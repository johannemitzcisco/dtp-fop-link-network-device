module dtp-fo-link-physical {

  namespace "http://www.cisco.com/dtp-fo-link-physical";
  prefix dtp-fo-link-physical;

  import dtp-network { prefix dtpn; }
  import ietf-inet-types { prefix inet; }
  import tailf-common { prefix tailf; }
  import tailf-ncs { prefix ncs; }

  description
    "This is an add on model to the dtp-network package/service";

  revision 2017-11-28 {
    description
      "Initial revision.";
  }

  augment /dtpn:dtp/dtpn:network/dtpn:topology/dtpn:link/dtpn:side/dtpn:side-type/dtpn:side-type {
    container physical {
      list port {
        min-elements 1;
        max-elements 2;
        key "port-type port-name";
        leaf port-type {
          type enumeration {
            enum "GigabitEthernet";
            enum "TenGigabitEthernet";
            enum "TenGigE";
            enum "FortyGigE";
            enum "HundredGigE";
          }
        }
        leaf port-name {
          type string;
        }
      }
    }
  }

}
