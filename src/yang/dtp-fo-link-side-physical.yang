module dtp-fo-link-side-physical {

  namespace "http://www.cisco.com/dtp-fo-link-side-physical";
  prefix dtp-fo-link-side-physical;

  import dtp-network { prefix dtpn; }
  import ietf-inet-types { prefix inet; }
  import tailf-common { prefix tailf; }
  import tailf-ncs { prefix ncs; }

  description
    "This is an add on model to the dtp-network package/service";

  revision 2017-11-28 {
    description
      "Initial revision.";
  }

  typedef port-type {
    type enumeration {
//      enum "Ethernet";
      enum "GigabitEthernet";
//      enum "TenGigabitEthernet";
//      enum "TenGigE";
//      enum "FortyGigE";
//      enum "HundredGigE";
    }
  }

  augment /dtpn:dtp/dtpn:network/dtpn:topology/dtpn:link/dtpn:side/dtpn:side-type/dtpn:side-type {
    container physical {
      container port {
        leaf port-type {
          type port-type;
        }
        leaf port-name {
          type string;
        }
      }
    }
  }

  grouping fo-defs {
    list physical {
      key name;
      uses dtpn:function-object;
    }
  }

  grouping physical-objects {
    leaf ipv4-address {
      type inet:ipv4-address;
    }
    leaf ipv4-mask {
      type inet:ipv4-address;
    }
  }

  augment /dtpn:dtp/dtpn:network/dtpn:topology/dtpn:link/dtpn:side/dtpn:function-objects {
    list physical {
      max-elements 1;
      key "function-object-name";
      leaf function-object-name {
        type leafref {
          path "/dtpn:dtp/dtpn:function-object-definitions/dtpn:link/dtpn:side/physical/name";
        }
      }
      uses physical-objects;
    }
  }

  augment /dtpn:dtp/dtpn:function-object-definitions/dtpn:link/dtpn:side {
    uses fo-defs;
  }

}
