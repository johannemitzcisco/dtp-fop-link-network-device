module dtp-fo-link-side-logical {

  namespace "http://www.cisco.com/dtp-fo-link-side-logical";
  prefix dtp-fo-link-side-logical;

  import dtp-network { prefix dtpn; }
  import ietf-inet-types { prefix inet; }
  import tailf-common { prefix tailf; }
  import tailf-ncs { prefix ncs; }

  description
    "This is an add on model to the dtp-network package/service";

  revision 2017-11-28 {
    description
      "Initial revision.";
  }

  typedef port-type {
    type enumeration {
      enum "Loopback";
    }
  }

  augment /dtpn:dtp/dtpn:network/dtpn:topology/dtpn:link/dtpn:side/dtpn:side-type/dtpn:side-type {
    container logical {
      container port {
        leaf port-type {
          type port-type;
        }
        leaf port-name {
          type string;
        }
      }
    }
  }

}
